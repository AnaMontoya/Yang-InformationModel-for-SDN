submodule ietf-NetInterASAdapterService {
	yang-version 1.1;
	belongs-to ietf-SystemIM {
    	prefix "NtAppAdptSrv";
	}

	include ietf-AdapterServices;
	include ietf-ServiceAccessPoint;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the AdapterService
		for the Network InterAS elements";

	revision 2017-04-12 {
		description "Initial revision.";
		reference "RFC 7950 - The YANG 1.1 Data Modeling Language";
	}

	leaf-list netInterASAdapterService {
		type identityref {
			base NetInterASAdapterServices;
		}
		description "A representation of the Adapter for NetInterAS itself";
	}

	leaf-list ProvidesEnpoint_NtInterASAdptSrv {
		type union {
			type identityref {
				base ProvidesEndpoint;
			}
			type NetInterASMI;
		}
		description "Represents the relationship between ServiceAccessPoint
		by the ProvidesEnpoint through the NetInterASMI";
	}

	leaf-list ServiceSAPDependency_NtInterASAdptSrv {
		type union {
			type identityref {
				base ServiceSAPDependency;
			}
			type NetInterASMI;
		}
		description "Represents the relationship between ServiceAccessPoint
		by the ProvidesEnpoint through the NetInterASMI";
	}
}
