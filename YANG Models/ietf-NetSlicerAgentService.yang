submodule ietf-NetSlicerAgentService {
	yang-version 1.1;
	belongs-to ietf-SystemIM {
		prefix "NetSlicerAgntServYang";
	}

	include ietf-AgentServices;
	include ietf-ServiceAccessPoint;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodel that represents Agent running on the managed 
	Network Slicer resources, models the management functions in accordance 
	with the managed resources of the Control Plane";

	revision 2017-04-12 {
		description "Initial revision.";
		reference "RFC 7950 - The YANG 1.1 Data Modeling Language";
	}

	leaf-list netSlicerAgentService {
		type identityref {
			base NetSlicerAgentServices;
		}
		description "Represents an istance of itself";
	}

	leaf-list ProvidesEnpoint_NtSlicerAgntSrv{
		type union{
			type identityref{
				base ProvidesEndpoint;
			}
			type NetSlicerMI;
		}
		description "Models the communication point from NetSlicerAgentService to
		NetSlicerAdapterService by the ServiceAccessPoint tagged as NetSlicerMI";
	}

	leaf-list ServiceSAPDependency_NtSlicerAgntSrv{
		type union{
			type identityref{
				base ServiceSAPDependency;
			}
			type NetSlicerMI;
		}
		description "Models the communication point from NetSlicerAgentService to
		NetSlicerAdapterService by the ServiceAccessPoint tagged as NetSlicerMI";

	}
}
