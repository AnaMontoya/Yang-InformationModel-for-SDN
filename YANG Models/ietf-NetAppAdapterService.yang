submodule ietf-NetAppAdapterService {
	yang-version 1.1;
	belongs-to ietf-SystemIM {
    	prefix "NtAppAdptSrv";
	}

	include ietf-NetApp;
	include ietf-AdapterServices;
	include ietf-ServiceAccessPoint;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the AdapterService
		for the Network Application elements";

	revision 2017-04-12 {
		description "Initial revision.";
		reference "RFC 7950 - The YANG 1.1 Data Modeling Language";
	}

	leaf-list netAppAdapterService{
		type identityref {
			base NetAppAdapterServices;
		}
		description "Inherits the defintion of AdapterService, 
		it is related to the Adapter for the NetApps in the 
		Application Plane";
	}

	leaf-list ProvidesEnpoint_NtAppAdptSrv{
		type union{
			type identityref{
				base ProvidesEndpoint;
			}
			type NetAppMI;
		}
		description "Relates the AdapterServices to the 
		ManagementServices by the ServiceAccessPoint 
		tagged as NetAppMI";
	}

	leaf-list ServiceSAPDependency_NtAppAdptSrv{
		type union{
			type identityref{
				base ServiceSAPDependency;
			}
			type NetAppMI;
		}
		description "Relates the AdapterServices to the 
		ManagementServices by the ServiceAccessPoint 
		tagged as NetAppMI";
	}
}
