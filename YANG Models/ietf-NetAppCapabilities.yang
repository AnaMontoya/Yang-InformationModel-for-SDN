submodule ietf-NetAppCapabilities{
	yang-version 1.1;
	belongs-to ietf-SystemIM{
		prefix "NetAppCp";
	}

	include ietf-NetApp;
	include ietf-NetAppSettings;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule for modeling the supported and excluded capabilities 
	of network applications";

	revision 2017-04-12 {
		description "Initial revision.";
		reference "RFC 7950 - The YANG 1.1 Data Modeling Language";
	}

	leaf ElementCapabilities_NetApp {
		type leafref {
			path "/netApp";
		}
		description "Referred to the netApp node for representing the relationship 
		between NetAppCapabilities and NetApp submodules";
	}
	leaf-list SettingsDefineCapabilities_NetApp {
		type leafref {
			path "/NetAppConfParameters";
		}
		description "Referred to the NetAppConfParameters node for representing the 
		relationship with the NetAppSettings submodule";
	}
}
