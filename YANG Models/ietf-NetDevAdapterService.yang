submodule ietf-NetDevAdapterService {
	yang-version 1.1;
	belongs-to ietf-SystemIM {
    	prefix "NtDevAdptSrv";
	}

	include ietf-NetApp;
	include ietf-AdapterServices;
	include ietf-ServiceAccessPoint;
	
	organization "University of Cauca";
	contact 
		"Ana Montoya 
		Phone: +57 301 630 9733
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the AdapterService
		for the Network Devices";

	revision 2017-04-12 {
		description "Initial revision.";
		reference "RFC 7950 - The YANG 1.1 Data Modeling Language";
	}

	leaf-list netDevAdapterService {
		type identityref {
			base NetDevAdapterServices;
		}
		description "A representation of the Adapter for NetDevs itself.";
	}

	leaf-list ProvidesEnpoint_NtDevAdptSrv {
		type union {
			type identityref {
				base ProvidesEndpoint;
			}
			type NetDevMI;
		}
		description "Represents the relationship between ServiceAccessPoint
		by the ProvidesEnpoint through the NetDevMI";
	}

	leaf-list ServiceSAPDependency_NtDevAdptSrv {
		type union {
			type identityref {
				base ServiceSAPDependency;
			}
			type NetDevMI;
		}
		description "Represents the relationship to ietf-ServiceAccessPoint
		by the ServiceSAPDependency through the NetDevMI";
	}
}
