submodule ietf-NetDevServiceSettings {
	yang-version 1.1;
	belongs-to ietf-SystemIM {
		prefix "NetDevServSt";
	}
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the configuration parameters of
	the NetDevs";

	revision 2017-04-12 {
		description "Initial revision.";
		reference "RFC 7950 - The YANG 1.1 Data Modeling Language";
	}

	leaf-list NetDevServParameters {
		type string;
		description "Defines the parameters that follow the services offered by 
		the NetDevs";
	}
}
