submodule ietf-ApplicationService {
	yang-version 1.1;
	belongs-to ietf-SystemIM {
		prefix "AppServYang";
	}

	include ietf-NOSService;
	include ietf-ServiceAccessPoint;

	organization "University of Cauca";
	contact 
		"Ana Montoya 
		Phone: +57 301 630 97331
		Email: anitamont7@gmail.com

		Daniela M. Casas
		Phone: +57 317 777 7225
		Email: danielacasas_@ieee.org
		
		Oscar Mauricio Caicedo
		Phone: +57 +57 310 491 8132
		Email: omcaicedo@unicauca.edu.co

		University of Cauca 
		Calle 5 #4-70 Popayán, Cauca
		Colombia";

	description "Submodule that represents services that expose functionality
	to the Application Plane";

	revision 2017-04-12 {
		description "Initial revision.";
		reference "RFC 7950 - The YANG 1.1 Data Modeling Language";
	}

	leaf-list applicationService {
		type identityref {
			base ApplicationService;
		}
		description "Referred to its corresponding identity in the 
		NOSService submodule for representing an instance of itself";
	}
	leaf-list ProvidesEndpoint_AppServ {
		type union {
			type identityref {
				base ProvidesEndpoint;
			}
			type NorthboundInterface;
		}
		description "Represents the communication point with entities from the 
		Application Plane by the NorthboundInterface";
	}
	leaf-list ServiceSAPDependency_AppServ {
		type union {
			type identityref {
				base ServiceSAPDependency;
			}
			type NorthboundInterface;
		}
		description "Represents the communication point with entities from the 
		Application Plane by the NorthboundInterface";
	}
}
