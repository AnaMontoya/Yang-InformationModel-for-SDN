submodule ietf-NOS {
	yang-version 1.1;
	belongs-to ietf-SystemIM {
    	prefix "NOSYang";
	}

	include ietf-NetApp;
	include ietf-NOSAgentService;
	include ietf-NOSService;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the well-known NOSs where the network applications run
	(e.g., OpenDaylight, Ryu and ONOS)";

	revision 2017-04-12 {
		description "Initial revision.";
		reference "RFC 7950 - The YANG 1.1 Data Modeling Language";
	}

	leaf-list Nos {
		type string;
		description "Represents an instance of itself";
	}
	leaf NetAppHostedOnNOS {
		type leafref{
			path "/netApp";
		}
		description "Represents the relationship between the NetApp and the NOS represents 
		local NetApps running on a NOS";
	}
	leaf HostService_NOSAgntServ {
		type leafref {
			path "/nosAgentService";
		}
		description "Represents that NOS is the hosting system for the NOSAgentService";
	}
	leaf HostedService_NOSServ {
		type identityref {
			base NOSService;
		}
		description "Represents the relationship between the NetApp and the Server models NetApps running 
		on remote servers";
	}
}
