submodule ietf-ManagementService {
	yang-version 1.1;
	belongs-to ietf-SystemIM {
		prefix "MngtSrvYang";
	}
	
	include ietf-ServiceAccessPoint;
	include ietf-StandarizedYangModules;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co
		
		University of Cauca 
		Calle 5 #4-70 Popayán, Cauca
		Colombia";

	description "Submodule that represents the Management Services
	(e.g., FCAPS+Programming) that allow carrying out different SDN
	management functions in the Management Plane of SDN";

	revision 2017-04-12 {
		description "Initial revision.";
		reference "RFC 7950 - The YANG 1.1 Data Modeling Language";
	}

	leaf MngtServ{
		type string;
		description "Represents an instance of itself which allows 
		establishing relationships with other nodes";
	}

	leaf-list ProvidesEndpoint_MngtServ{
		type union {
			type identityref{
				base ProvidesEndpoint;
			}
			type AdapterInterface;
		}
		description "Relationship for indicating that the nodes 
		related establish their own communication point to access 
		from the other one";
	}

	leaf-list ServiceSAPDependency_MngtServ{
		type union {
			type identityref{
				base ServiceSAPDependency;
			}
			type AdapterInterface;
		}
		description "Relationship for implying that both nodes related 
		use the ServiceAccessPoint to access the other one";
	}

	leaf-list ToYangRepository {
		type leafref {
			path "/KnownModules";
		}
		description "Relationship that relates ManagementServices submodule
		with StandarizedYANGModules submodule to consider well-known YANG modules";
	}	

	container ElementCapabilities {
		description "Relationship representing the capabilities supported for Services.";
		leaf FaultService {
			type string;
			description "Defines the supported and excluded capabilities for the FaultService";
		}
		leaf ConfigurationService {
			type string;
			description "Defines the supported and excluded capabilities for the ConfigurationService";
		}
		leaf AccountingService {
			type string;
			description "Defines the supported and excluded capabilities for the AccountingService";
		}
		leaf PerformanceService {
			type string;
			description "Defines the supported and excluded capabilities for the PerformanceService";
		}
		leaf SecurityService {
			type string;
			description "Defines the supported and excluded capabilities for the SecurityService";
		}
		leaf ProgrammingService {
			type string;
			description "Defines the supported and excluded capabilities for the ProgrammingService";
		}
	}
}
