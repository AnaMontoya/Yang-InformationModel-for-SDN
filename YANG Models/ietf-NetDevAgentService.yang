submodule ietf-NetDevAgentService {
	yang-version 1.1;
	belongs-to ietf-SystemIM {
		prefix "NetDevAgntSrv";
	}

	include ietf-AgentServices;
	include ietf-ServiceAccessPoint;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the Agent running on the 
		the managerd Network Devices";

	revision 2017-04-12 {
		description "Initial revision.";
		reference "RFC 7950 - The YANG 1.1 Data Modeling Language";
	}

	leaf-list netDevAgentService {
		type identityref {
			base NetDevAgentServices;
		}
		description "Represents an istance of itself";
	}

	leaf netDevAgentPort{
		type uint16;
		description "Specifies the communication port that the Agent uses";
	}

	leaf-list ProvidesEnpoint_NtADevAgntSrv {
		type union {
			type identityref {
				base ProvidesEndpoint;
			}
			type NetDevMI;
		}
		description "Models the communication point from NetDevAgentService to
		NetDevdapterService by the ServiceAccessPoint tagged as NetDevMI";
	}

	leaf-list ServiceSAPDependency_NtDevAgntSrv {
		type union {
			type identityref {
				base ServiceSAPDependency;
			}
			type NetDevMI;
		}
		description "Models the communication point from NetDevAgentService to
		NetDevdapterService by the ServiceAccessPoint tagged as NetDevMI";
	}
}
