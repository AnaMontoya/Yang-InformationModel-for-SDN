submodule ietf-ProcessIndications {
	yang-version 1.1;
	belongs-to ietf-SystemIM {
		prefix "PrcssIndYang";
	}
	
	organization "University of Cauca";
	contact 
		"Ana Montoya 
		Phone: +57 301 630 97331
		Email: anitamont7@gmail.com

		Daniela M. Casas
		Phone: +57 317 777 7225
		Email: danielacasas_@ieee.org

		University of Cauca 
		Calle 5 #4-70 Popayán, Cauca
		Colombia";

	description "";

	revision 2017-04-12 {
		description "Initial revision.";
		reference "RFC 7950 - The YANG 1.1 Data Modeling Language";
	}

	identity ProcessIndication {
		description "Respresents an instance of the process for notifications";
	}
	identity Notification {
		base PrcssIndYang:ProcessIndication;
		description "Represents an instance of the notifications";
	}

	notification event {
		description "Unresquested messages with information about SDN managed resources";
		leaf eventDescription {
			type string;
			description "";
		}
		leaf reporting-entity {
			type instance-identifier;
			description "";
		}
		leaf severity {
			type string;
			description "";
		}
	}
	leaf AgentID{
		type string;
		description "";
	}
}
