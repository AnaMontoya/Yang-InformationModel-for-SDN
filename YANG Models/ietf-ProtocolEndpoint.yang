submodule ietf-ProtocolEndpoint{
	yang-version 1.1;
	belongs-to ietf-SystemIM {
		prefix "ProEndpointYang";
	}
	
	include ietf-ManagementService;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the communication point allowing the 
	access of Administrators to networks (e.g., a Configuration Service provides
	an HTTP interface as an API to allow Network Administrators to set SBI 
	parameters of NetDevs by a Web browser)";

	revision 2017-04-12 {
		description "Initial revision.";
		reference "RFC 7950 - The YANG 1.1 Data Modeling Language";
	}

	choice ProvidesEndpoint_ProEndpoint{
		leaf Fault_GUI {
			type leafref {
				path "/ElementCapabilities/FaultService";
			}
			description "Represents the User Interface for the Fault Service";
		}
		leaf Configuration_GUI {
			type leafref {
				path "/ElementCapabilities/ConfigurationService";
			}
			description "Represents the User Interface for the Configuration Service";
		}
		leaf Accounting_GUI {
			type leafref {
				path "/ElementCapabilities/AccountingService";
			}
			description "Represents the User Interface for the Accounting Service";
		}
		leaf Performance_GUI {
			type leafref {
				path "/ElementCapabilities/PerformanceService";
			}
			description "Represents the User Interface for the Performance Service";
		}
		leaf Security_GUI {
			type leafref {
				path "/ElementCapabilities/SecurityService";
			}
			description "Represents the User Interface for the Security Service";
		}
		leaf Programming_GUI {
			type leafref {
				path "/ElementCapabilities/ProgrammingService";
			}
			description "Represents the User Interface for the Programming Service";
		}
		description "Models User Interfaces per Management Service with a leaf 
		per interface that may be chosen and used by the network administrator.";
	}
}
