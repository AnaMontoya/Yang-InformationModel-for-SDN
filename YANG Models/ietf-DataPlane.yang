submodule ietf-DataPlane{
yang-version 1.1;
	belongs-to ietf-SystemIM{
		prefix "DataPlaneYang";
	}

	include ietf-NetDev;

	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co
		
		University of Cauca 
		Calle 5 #4-70 Popayán, Cauca
		Colombia";

	description "Submodule that represents the Data plane to 
	be managed by the Management Plane";

	revision 2017-04-12 {
		description "Initial revision.";
		reference "RFC 7950 - The YANG 1.1 Data Modeling Language";
	}

	leaf NetworkDomain{
		type string;
		description "Represents the domain to which the Data
		Plane to be managed belongs";
	}
	leaf-list DataPlane{
		type leafref{
			path "/NetworkDomain";
		}
		description "Represents an instance of the Data Plane 
		related to the Network domain";
	}
	container SystemComponent_DtPlane{
		description "Relationship that describes that the DataPlane 
		is formed by one or more NetDevs";
		leaf-list DataPlane_NetDev{
			type leafref{
				path "/netDev";
			}
			description "Represents new instances of NetDevs that may
			 be added to the Data Plane";
		}
	}

}
