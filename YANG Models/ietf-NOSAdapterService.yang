submodule ietf-NOSAdapterService {
	yang-version 1.1;
	belongs-to ietf-SystemIM {
		prefix "NOSAdptSrv";
	}

	include ietf-ServiceAccessPoint;
	include ietf-AdapterServices;	
	include ietf-NOS;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodel that represents the Adapter to communicate
	with the managed NOS from the Management Plane";

	revision 2017-04-12 {
		description "Initial revision.";
		reference "RFC 7950 - The YANG 1.1 Data Modeling Language";
	}

	leaf-list NOSAdapterService {
		type identityref {
			base NOSAdapterServices;
		}
		description "Inherits the defintion of AdapterService, 
		it is related to the Adapter for the NOSs in the Control Plane";
	}

	leaf-list ProvidesEnpoint_NOSAdptSrv{
		type union{
			type identityref{
				base ProvidesEndpoint;
			}
			type NetNOSMI;
		}
		description "Relates the AdapterServices to the 
		ManagementServices by the ServiceAccessPoint 
		tagged as NetNOSMI";
	}

	leaf-list ServiceSAPDependency_NOSAAdptSrv{
		type union{
			type identityref{
				base ServiceSAPDependency;
			}
			type NetNOSMI;
		}
		description "Relates the AdapterServices to the 
		ManagementServices by the ServiceAccessPoint 
		tagged as NetNOSMI";
	}
}
