submodule ietf-NetAppAgentService {
	yang-version 1.1;
	belongs-to ietf-SystemIM {
    	prefix "NtAppAgntSrv";
	}

	include ietf-AgentServices;
	include ietf-ServiceAccessPoint;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodel that represents Agent running on the managed 
	Network Applications";

	revision 2017-04-12 {
		description "Initial revision.";
		reference "RFC 7950 - The YANG 1.1 Data Modeling Language";
	}

	leaf-list netAppAgentService{
		type identityref {
			base NetAppAgentServices;
		}
		description "Represents an istance of itself";
	}

	leaf-list ProvidesEnpoint_NtAppAgntSrv{
		type union{
			type identityref{
				base ProvidesEndpoint;
			}
			type NetAppMI;
		}
		description "Models the communication point from NetAppAgentService to
		NetAppAdapterService by the ServiceAccessPoint tagged as NetAppMI";
	}

	leaf-list ServiceSAPDependency_NtAppAgntSrv{
		type union{
			type identityref{
				base ServiceSAPDependency;
			}
			type NetAppMI;
		}
		description "Models the communication point from NetAppAgentService to
		NetAppAdapterService by the ServiceAccessPoint tagged as NetAppMI";
	}
}
