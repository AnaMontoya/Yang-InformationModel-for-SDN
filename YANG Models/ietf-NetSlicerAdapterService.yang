submodule ietf-NetSlicerAdapterService {
	yang-version 1.1;
	belongs-to ietf-SystemIM {
    	prefix "NtSlcrAdptSrv";
	}
	
	include ietf-NetSlicer;
	include ietf-AdapterServices;
	include ietf-ServiceAccessPoint;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the AdapterService
		for the Network Slicer elements";

	revision 2017-04-12 {
		description "Initial revision.";
		reference "RFC 7950 - The YANG 1.1 Data Modeling Language";
	}

	leaf-list netSlicerAdapterService{
		type identityref {
			base NetSlicerAdapterServices;
		}
		description "Inherits the defintion of AdapterService, 
		it is related to the Adapter for the Slicers in the Control Plane";
	}

	leaf-list ProvidesEnpoint_NtSlicerAdptSrv{
		type union{
			type identityref{
				base ProvidesEndpoint;
			}
			type NetSlicerMI;
		}
		description "Represents the relationship between ServiceAccessPoint
		by the ProvidesEnpoint through the NetDev NetSlicerMI";
	}

	leaf-list ServiceSAPDependency_NtSlicerAdptSrv{
		type union{
			type identityref{
				base ServiceSAPDependency;
			}
			type NetSlicerMI;
		}
		description "Represents the relationship between ServiceAccessPoint
		by the ProvidesEnpoint through the NetDev NetSlicerMI";
	}
}
