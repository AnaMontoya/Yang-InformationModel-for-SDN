submodule ietf-InterASService {
	yang-version 1.1;
	belongs-to ietf-SystemIM {
		prefix "InterASSrv";
	}

	include ietf-ServiceAccessPoint;
	include ietf-InterASSettings;
	include ietf-InterASCapabilities;

	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that models the service that allows managing
communication between different network domains";

	revision 2017-04-12 {
		description "Initial revision.";
		reference "RFC 7950 - The YANG 1.1 Data Modeling Language";
	}

	leaf-list ElementSettingData_InterAS {
		type leafref{
			path "/InterASConfParameters";
		}
		description "Referred to the InterASConfParameters node for representing the 
		relationship with the InterASSettings";
	}
	leaf-list interASService{
		type string;
		description "Represents an instance of itself";
	} 
	leaf-list ProvidesEndpoint_InterASServ{
		type union{
			type SouthboundInterface;
			type identityref{
				base ProvidesEndpoint;
			}
		}
		description "Relationship that represents the communication point with other elements 
		located in the Data Plane";
	}
	leaf-list ServiceSAPDependency_InterASServ{
		type union{
			type SouthboundInterface;
			type identityref{
				base ServiceSAPDependency;
			}
		}
		description "Relationship that represents the communication point with other elements 
		located in the Data Plane";
	}
	leaf-list ElementCapabilities_InterASCap {
		type leafref{
			path "/interASCapabilities";
		}
		description "referred to the interASCapabilities node for representing the relationship 
		with the InterASCapabilities";
	}
}
