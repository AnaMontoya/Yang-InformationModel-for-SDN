submodule ietf-NOSService {
	yang-version 1.1;
	belongs-to ietf-SystemIM {
		prefix "NOSServYang";
	}

	include ietf-NOSServiceCapabilities;
	include ietf-NOSServiceSettings;

	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents network services hosted
	in a NOS";

	revision 2017-04-12 {
		description "Initial revision.";
		reference "RFC 7950 - The YANG 1.1 Data Modeling Language";
	}

	identity NOSService {
		description "Inherits its nature to the ApplicationService, 
		DistributingService and ControlService identities for representing 
		the services offered by the NOS";
	}
	identity ApplicationService {
		base NOSServYang:NOSService;
		description "Represents the Aplication Services offered by the NOS";
	}
	identity DistributingService {
		base NOSServYang:NOSService;
		description "Represents the Distributing Services offered by the NOS";
	}
	identity ControlService {
		base NOSServYang:NOSService;
		description "Represents the Control Services offered by the NOS";
	}

	leaf ElementCapabilities_NOSServ {
		type leafref {
			path "/nosServiceCapabilities";
		}
		description "Referred to the nosServiceCapabilities node for representing 
		the relationship with the NOSServiceCapabilities submodule";
	}
	leaf-list ElementSettingData_NOSServ {
		type leafref {
			path "/NOSConfParameters";
		}
		description "Referred to the NOSConfParameters node for describing the 
		relationship with the NOSServiceSettings submodule";
	}
	leaf-list ServiceServiceDependency {
		type identityref {
			base NOSService;
		}
		description "Referred to the NOSService \textit{identity} for representing 
		the relatinship with the NOSService itself";
	}
}
