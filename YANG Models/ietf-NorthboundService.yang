submodule ietf-NorthboundService {
	yang-version 1.1;
	belongs-to ietf-SystemIM {
		prefix "NbSrv";
	}
	
	include ietf-ServiceAccessPoint;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the communication with services 
	exposed by a NOS (e.g., a NetApp that performs load-balancing and 
	access-control functionality by retrieving and supplying data for tracking 
	and firewall services deployed on the top of a NOS)";

	revision 2017-04-12 {
		description "Initial revision.";
		reference "RFC 7950 - The YANG 1.1 Data Modeling Language";
	}

	leaf-list northboundService {
		type string;
		description "Represents an istance of itself";
	}
	leaf-list ServiceSAPDependency_NBS {
		type union {
			type identityref {
				base ServiceSAPDependency;
				}
			type NorthboundInterface;
			}
		description "Models the communication point provided by the ServiceAccessPoint 
		tagged as NorthboundInterface, reflects that the NorthboundService uses this 
		communication point";
	}
	leaf-list ProvidesEndpoint_NBS {
		type union{
			type identityref{
				base ProvidesEndpoint;
				}
			type NorthboundInterface;
			}
		description "Models the communication point provided by the ServiceAccessPoint 
		tagged as NorthboundInterface, reflects that the NorthboundService uses this 
		communication point";
	}

}
