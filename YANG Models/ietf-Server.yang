submodule ietf-Server{
	yang-version 1.1;
	belongs-to ietf-SystemIM{
    	prefix "SrvrYang";
	}

	include ietf-NetApp;

	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that models the NetApps running on remote
	servers where such remote NetApps prefer NBIs based on protocols 
	for communicating with the Control Plane than NBIs based on NOS native 
	bundles";

	revision 2017-04-12 {
		description "Initial revision.";
		reference "RFC 7950 - The YANG 1.1 Data Modeling Language";
	}

	leaf NetAppHostedOnServer{
		type leafref{
			path "/netApp";
		}
		description "Represents the relationship between the NetApp and the 
		Server models NetApps running on remote servers";
	}
}
