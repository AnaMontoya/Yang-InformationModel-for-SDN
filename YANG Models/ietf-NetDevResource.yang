submodule ietf-NetDevResource {
	yang-version 1.1;
	belongs-to ietf-SystemIM {
		prefix "NetDevRsc";
	}

	include ietf-StatisticalData;
	include ietf-NetDevResourceSettings;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that models network elements 	composing 
	a NetDev, like ports, queues, and tables";

	revision 2017-04-12 {
		description "Initial revision.";
		reference "RFC 7950 - The YANG 1.1 Data Modeling Language";
	}

	leaf-list netDevResource {
		type string;
		description "Implies the aggregation with NetDev";
	}

	container Component {
		leaf-list Resources {
			type leafref {
				path "/netDevResource";
			}
			description "Connects to the NetDevResource models a 
			network element composed of others, such as ports 
			including various queues";
		}
		description "";
	}
	leaf-list ElementSettingData_NetDevRsrc {
		type leafref {
			path "/NetDevConfParameters";
		}
		description "Reflects the relationship between 
		NetDevResourceSettings and the NetDevResource";
	}
	leaf-list Statistics {
		type leafref {
			path "/Statistics_NetDevRsrc";
		}
		description "Attaches the NetDevResourceStatistics 
		with the NetDevResource";
	}

	leaf ResourceType {
		type uint16;
		description "Allows to identify the type of network element 
		composing the NetDev";
	}

}
