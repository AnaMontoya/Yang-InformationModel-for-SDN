submodule ietf-NetDevCapabilities {
	yang-version 1.1;
	belongs-to ietf-SystemIM {
		prefix "NetDevRsrcSt";
	}

	include ietf-NetDev;
	include ietf-NetDevResourceSettings;
	include ietf-NetDevServiceSettings;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule for describing supported and excluded 
	capabilities of a network device";

	revision 2017-04-12 {
		description "Initial revision.";
		reference "RFC 7950 - The YANG 1.1 Data Modeling Language";
	}

	leaf ElementCapabilities_NetDev {
		type leafref {
			path "/netDevs";
		}
		description "Referred to the netDev node to represent its 
		relationship with NetDevs";
	}
	leaf-list SettingsDefineCapabilities_NetDevSt {
		type leafref {
			path "/NetDevConfParameters";
		}
		description "Referred to the NetDevConfParameters node to 
		define the relationship with the NetDevResourceSettings submodule";
	}
	leaf-list SettingsDefineCapabilities_NetDevSvc {
		type leafref {
			path "/NetDevServParameters";
		}
		description "Referred to the NetDevServParameters node for 
		representing the relationship with the NetDevCapabilities submodule";
	}
}
