submodule ietf-ControlService {
	yang-version 1.1;
	belongs-to ietf-SystemIM {
		prefix "CtrlServYang";
	}

	include ietf-NOSService;
	include ietf-ServiceAccessPoint;

	organization "University of Cauca";
	contact 
		"Ana Montoya 
		Phone: +57 301 630 97331
		Email: anitamont7@gmail.com

		Daniela M. Casas
		Phone: +57 317 777 7225
		Email: danielacasas_@ieee.org

		University of Cauca 
		Calle 5 #4-70 Popayán, Cauca
		Colombia";

	description "";

	revision 2017-04-12 {
		description "Initial revision.";
		reference "RFC 7950 - The YANG 1.1 Data Modeling Language";
	}

	leaf-list controlService {
		type identityref {
			base ControlService;
		}
		description "";
	}

	leaf-list ProvidesEndpoint_CtrlServ {
		type union {
			type identityref {
				base ProvidesEndpoint;
			}
			type SouthboundInterface;
		}
		description "";
	}
	leaf-list ServiceSAPDependency_CtrlServ {
		type union {
			type identityref {
				base ServiceSAPDependency;
			}
			type SouthboundInterface;
		}
		description "";
	}
}
