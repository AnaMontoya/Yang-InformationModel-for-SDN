submodule ietf-AppPlane {
yang-version 1.1;
	belongs-to ietf-SystemIM {
		prefix "AppPlaneYang";
	}

	include ietf-NetApp;
	
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that represents the Application plane to 
	be managed by the Management Plane";

	revision 2017-04-12 {
		description "Initial revision.";
		reference "RFC 7950 - The YANG 1.1 Data Modeling Language";
	}
	
	leaf NetAppDomain {
		type string;
		description "Represents the domain to which the Application
		Plane to be managed belongs";
	}
	leaf AppPlane {
		type leafref {
			path "/NetAppDomain";
		}
		description "Represents an instance of the Application Plane 
		related to the NetApp domain";
	}

	container SystemComponent_AppPlane {
		
		leaf AppPlane_NetApp {
			type leafref {
				path "/netApp";
			}
			description "Represents new instances of NetApp that may
			 be added to the Application Plane";
		description "Relationship that describes that the AppPlane 
		is formed by one or more NetApps";
		}
	}
}
