submodule ietf-SlicingStatistics {
	yang-version 1.1;
	belongs-to ietf-SystemIM {
		prefix "SlicingStatYang";
	}
	include ietf-SlicingService;
	include ietf-StatisticalData;
	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that models collections of
metrics for instances of a SlicingService";

	revision 2017-04-12 {
		description "Initial revision.";
		reference "RFC 7950 - The YANG 1.1 Data Modeling Language";
	}

	leaf-list ServiceStatistics {
		type leafref {
			path "/Slices";
		}
		description "Referred to the Slices node for representing the relationship with 
		the SlicingStatistics submodule";
	}
	leaf-list SlicingStatistics {
		type identityref {
			base SlicingStatistics;
		}
		description "referred to the SlicigStatistics identity for relating with the SlicingService 
		submodule";
	}
	leaf TotalSlices {
		type uint32;
		description "Defines the total number of slices handled by a NetSlicer";
	}

}
