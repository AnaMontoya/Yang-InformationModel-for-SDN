submodule ietf-InterAS {
	yang-version 1.1;
	belongs-to ietf-SystemIM {
		prefix "InterASYang";
	}
	
	include ietf-NetInterASAgentService;
	include ietf-InterASService;

	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that models the communications between
	Autonomous Systems";

	revision 2017-04-12 {
		description "Initial revision.";
		reference "RFC 7950 - The YANG 1.1 Data Modeling Language";
	}

	leaf-list interAS {
		type string;
		description "Represents an instance of itself";
	}
	leaf-list HostService_NetInterASAgntServ {
		type leafref {
			path "/netInterASAgentService";
		}
		description "Referred to the netInterASAgentService node to describe 
		the relationship with the NetInterASAgentService submodule";
	} 
	leaf-list HostService_InterASServ {
		type leafref {
			path "/interASService";
		}
		description "Referred to the interASService node to represent the relationship 
		with the InterASService submodule";
	}
}
