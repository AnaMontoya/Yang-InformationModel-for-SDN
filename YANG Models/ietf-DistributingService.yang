submodule ietf-DistributingService {
	yang-version 1.1;
	belongs-to ietf-SystemIM{
		prefix "DistribServYang";
	}

	include ietf-NOSService;
	include ietf-ServiceAccessPoint;

	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co

		University of Cauca 
		Calle 5 #4-70 Popayán, Cauca
		Colombia";

	description "Submodule that models the service that allows managing any distributed 
	Control Plane";

	revision 2017-04-12 {
		description "Initial revision.";
		reference "RFC 7950 - The YANG 1.1 Data Modeling Language";
	}
	leaf-list distributingService {
		type identityref {
			base DistributingService;
		}
		description "Referred to its corresponding identity in the NOSService 
		submodule to represent an instance of itself";
	}

	leaf-list ProvidesEndpoint_DistribServ {
		type union {
			type identityref {
				base ProvidesEndpoint;
			}
			type East-WestboundInterface;
		}description "Represents the communication point with other entities from the 
		Control Plane by the East/WestboundInterface";
	}
	leaf-list ServiceSAPDependency_DistribServ {
		type union {
			type identityref {
				base ServiceSAPDependency;
			}
			type East-WestboundInterface;
		}
		description "Represents the communication point with other entities from the 
		Control Plane by the East/WestboundInterface";
	}
}
