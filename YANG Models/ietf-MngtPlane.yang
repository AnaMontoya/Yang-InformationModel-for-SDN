submodule ietf-MngtPlane{
yang-version 1.1;
	belongs-to ietf-SystemIM{
		prefix "MngtPlaneYang";
	}

	include ietf-NetApp;

	organization "University of Cauca";
	contact 
		"Ana Montoya 
		Phone: +57 301 630 97331
		Email: anitamont7@gmail.com

		Daniela M. Casas
		Phone: +57 317 777 7225
		Email: danielacasas_@ieee.org

		Oscar Mauricio Caicedo
		Phone: +57 +57 310 491 8132
		Email: omcaicedo@unicauca.edu.co
		
		University of Cauca 
		Calle 5 #4-70 Popayán, Cauca
		Colombia";

	description "Submodule that represents a Management plane to be managed belonging 
	to a different Autonomous System";

	revision 2017-04-12 {
		description "Initial revision.";
		reference "RFC 7950 - The YANG 1.1 Data Modeling Language";
	}

	leaf InterASDomain{
		type string;
		description "Represents the domain from a different Autonomous System to which 
		the Management Plane to be managed belongs";
	} 
	leaf-list MngtPlane{
		type leafref{
			path "/InterASDomain";
		}
		description "Represents an instance of the Management Plane related to the 
		InterAS domain from another Autonomous System";
	}
}
